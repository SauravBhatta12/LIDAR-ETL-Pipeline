FME workspace LIDAR-ETL-Pipeline.fmw

Parameters:
- SourceDataset_LAS = $(FME_MF_DIR)3dm_32_280_5652_1_nw.laz   # Source ASPRS LAS File(s)
- DestDataset_POSTGIS = Local_PostGIS   # Connection

Readers:
- LAS_1: LAS from $(SourceDataset_LAS)

Writers:
- POSTGIS_1: POSTGIS to $(DestDataset_POSTGIS)

LAS (reader LAS_1)
    -> PointCloudFilter
PointCloudFilter
    FILTER_TABLE = @Component(classification) == 2 Ground @Component(classification) == 6 Buildings
    OUTPUT_UNFILTERED_POINTS = Yes
    <UNFILTERED> -> PointCloudStatisticsCalculator_2
PointCloudStatisticsCalculator_2
    POINT_COMPONENTS = z         intensity
    -> CsmapReprojector
CsmapReprojector
    DEST = EPSG:4326
    INTERPOLATION_TYPE_NAME = NearestNeighbor
    RASTER_CELL_SIZE = PreserveCells
    RASTER_TOLERANCE = 0.0
    REPROJECTED -> PythonCaller
PythonCaller
    NEW_ATTRIBUTES = processed_timestamp datetime data_quality_status varchar(200) processed_point_count int32
    PYTHONSOURCE:
      import fme
      import fmeobjects
      from datetime import datetime

      class FeatureProcessor(object):
          def __init__(self):
              pass

          def input(self, feature):
              # 1. Get the number of points in this chunk
              # Note: FME handles point clouds as a single feature with complex geometry
              geometry = feature.getGeometry()
              if geometry:
                  point_count = geometry.getPointCount()
                  feature.setAttribute("processed_point_count", point_count)

              # 2. Add a processing timestamp
              now = datetime.now().strftime("%Y-%m-%d %H:%M:%S")
              feature.setAttribute("processed_timestamp", now)

              # 3. Add a "Quality Check" tag
              feature.setAttribute("data_quality_status", "Verified_Ground_Class")

              # Output the modified feature
              self.pyoutput(feature)

          def close(self):
              pass
    PYTHONSYMBOL = FeatureProcessor
    -> PointCloudToPointCoercer
PointCloudToPointCoercer
    ACCUM_ATTRS = YES
    CONVERT_TO = POINT
    PART_NUMBER_ATTR_NAME = _part_number
    POINT_COMPONENTS_PRESERVE_TYPE = ATTRIBUTES
    ACCUM_ATTRS_NAME = Yes
    CONVERT_TO_DISPLAY = Individual Points
    POINT_COMPONENTS_PRESERVE_DISPLAY = Attributes
    COERCED -> LIDAR_Ground_Points_Processed (writer POSTGIS_1)
LIDAR_Ground_Points_Processed (writer POSTGIS_1)
    attributes: processed_timestamp timestamp, data_quality_status varchar(200), processed_point_count int4
